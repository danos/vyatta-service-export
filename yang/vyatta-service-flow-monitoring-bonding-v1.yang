module vyatta-service-flow-monitoring-bonding-v1 {
	namespace "urn:vyatta.com:mgmt:vyatta-service-flow-monitoring-bonding:1";
	prefix vyatta-service-flow-monitoring-bonding-v1;

	import configd-v1 {
		prefix configd;
	}
	import vyatta-interfaces-v1 {
		prefix if;
	}
	import vyatta-interfaces-bonding-v1 {
		prefix if-bonding;
	}
	import vyatta-service-flow-monitoring-v1 {
		prefix flow-monitoring;
	}

	organization "AT&T Inc.";
	contact
	    "AT&T
	     Postal: 208 S. Akard Street
	             Dallas, TX 25202
	     Web: www.att.com";
	 
	description
	    "Copyright (c) 2019 AT&T Intellectual Property
	     All rights reserved.
	 
	     Copyright (c) 2015-2016 by Brocade Communications Systems, Inc.
	     All rights reserved.
	 
	     The YANG module for vyatta-service-flow-monitoring-bonding-v1
	 
	     Redistribution and use in source and binary forms, with or without
	     modification, are permitted provided that the following conditions
	     are met:
	 
	     1. Redistributions of source code must retain the above copyright
	        notice, this list of conditions and the following disclaimer.
	     2. Redistributions in binary form must reproduce the above
	        copyright notice, this list of conditions and the following
	        disclaimer in the documentation and/or other materials provided
	        with the distribution.
	     3. Neither the name of the copyright holder nor the names of its
	        contributors may be used to endorse or promote products derived
	        from this software without specific prior written permission.
	 
	     THIS SOFTWARE IS PROVIDED BY THE COPYRIGHT HOLDERS AND CONTRIBUTORS
	     'AS IS' AND ANY EXPRESS OR IMPLIED WARRANTIES, INCLUDING, BUT NOT
	     LIMITED TO, THE IMPLIED WARRANTIES OF MERCHANTABILITY AND FITNESS
	     FOR A PARTICULAR PURPOSE ARE DISCLAIMED. IN NO EVENT SHALL THE
	     COPYRIGHT HOLDER OR CONTRIBUTORS BE LIABLE FOR ANY DIRECT, INDIRECT,
	     INCIDENTAL, SPECIAL, EXEMPLARY, OR CONSEQUENTIAL DAMAGES (INCLUDING,
	     BUT NOT LIMITED TO, PROCUREMENT OF SUBSTITUTE GOODS OR SERVICES;
	     LOSS OF USE, DATA, OR PROFITS; OR BUSINESS INTERRUPTION) HOWEVER
	     CAUSED AND ON ANY THEORY OF LIABILITY, WHETHER IN CONTRACT, STRICT
	     LIABILITY, OR TORT (INCLUDING NEGLIGENCE OR OTHERWISE) ARISING IN
	     ANY WAY OUT OF THE USE OF THIS SOFTWARE, EVEN IF ADVISED OF THE
	     POSSIBILITY OF SUCH DAMAGE.
	 
	     SPDX-License-Identifier: BSD-3-Clause";

	revision 2015-09-09 {
		description "Vermont revision of version 1.";
		configd:migration 1;
	}

	augment /if:interfaces/if-bonding:bonding {
		uses flow-monitoring:interface-parameters;
	}
}
